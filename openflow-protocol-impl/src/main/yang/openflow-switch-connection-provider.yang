module openflow-switch-connection-provider {
	yang-version 1;
    namespace "urn:opendaylight:params:xml:ns:yang:openflow:switch:connection:provider";
    prefix "openflow-switch-connection-provider";

    import config {prefix config; revision-date 2013-04-05; }

    description
        "openflow-switch-connection-provider service definitions";

    revision "2014-03-28" {
        description
            "Initial revision";
    }

    identity openflow-switch-connection-provider {
         base "config:service-type";
         config:java-class "org.opendaylight.openflowjava.protocol.spi.connection.SwitchConnectionProvider";
    }
}
