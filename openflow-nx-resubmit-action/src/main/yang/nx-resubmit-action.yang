/*
 * Copyright (c) 2013 Pantheon Technologies s.r.o. and others. All rights reserved.
 *
 * This program and the accompanying materials are made available under the
 * terms of the Eclipse Public License v1.0 which accompanies this distribution,
 * and is available at http://www.eclipse.org/legal/epl-v10.html
 */
 
 module nx-resubmit-action {
    namespace "urn:opendaylight:openflow:nx:resubmit:action";
    prefix "nx-resubmit";

    import openflow-types {prefix oft;}
    import openflow-action {prefix ofaction;}
    import yang-ext {prefix ext;}

    revision "2013-07-31" {
        description "OpenFlow 1.3 - action model";
    }
    
    identity nx-resubmit-action {
        base ofaction:experimenter-action-sub-type;
    }

    augment "/ofaction:actions-container/ofaction:action" {
         ext:augment-identifier "nx-action-resubmit-augment";
         leaf subtype {
             type uint16;
         }
         leaf in-port {
             type uint16;
         }
         leaf table {
             type uint8;
         }
     }

}
