/*
 * Copyright (c) 2013 Pantheon Technologies s.r.o. and others. All rights reserved.
 *
 * This program and the accompanying materials are made available under the
 * terms of the Eclipse Public License v1.0 which accompanies this distribution,
 * and is available at http://www.eclipse.org/legal/epl-v10.html
 */
 
 module exemplary-action {
    namespace "urn:opendaylight:openflow:common:exaction";
    prefix "exaction";

    import openflow-types { prefix oft; }
    import openflow-action {prefix ofaction;}
    import yang-ext {prefix ext;}

    revision "2013-07-31" {
        description "OpenFlow 1.3 - action model";
    }

    identity nx-action-resubmit {
        base oft:action-base;
    }
    
    augment "/ofaction:actions-container/ofaction:action" {
         ext:augment-identifier "experimenter-action2";
         leaf experimenter {
             type uint32;
         }
         leaf data {
             type binary;
         }
     }
    augment "/ofaction:actions-container/ofaction:action" {
         ext:augment-identifier "nx-action-resubmit-augment";
         leaf vendor {
             type uint32;
         }
         leaf subtype {
             type uint16;
         }
         leaf in-port {
             type uint16;
         }
         leaf table {
             type uint8;
         }
     }

}
