/*
 * Copyright (c) 2014 Pantheon Technologies s.r.o. and others. All rights reserved.
 *
 * This program and the accompanying materials are made available under the
 * terms of the Eclipse Public License v1.0 which accompanies this distribution,
 * and is available at http://www.eclipse.org/legal/epl-v10.html
 */
 
 module openflow-configuration {
    namespace "urn:opendaylight:openflow:config";
    prefix "of-config";

    revision "2014-06-30" {
        description "Library configuration classes";
    }

    typedef path-type {
        type enumeration {
            enum CLASSPATH {
                value 0; 
                description "Keystore file is located on classpath.";
            }
            enum PATH {
                value 1; 
                description "Keystore file is located on absolute or relative path.";
            }
        }
    }

    typedef keystore-type {
        type enumeration {
            enum JKS {
                value 0; 
                description "Keystore type - JKS.";
            }
            enum PKCS12 {
                value 1; 
                description "Keystore type - PKCS12.";
            }
        }
    }

    typedef transport-protocol {
        type enumeration {
            enum TCP {
                value 0;
                description "Communication over TCP protocol.";
            }
            enum TLS {
                value 1;
                description "Communication over TLS protocol.";
            }
            enum UDP {
                value 2;
                description "Communication over UDP protocol.";
            }
        }
    }
}
