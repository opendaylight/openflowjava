/*
 * Copyright (c) 2016 Brocade Communications Systems, Inc. and others.  All rights reserved.
 *
 * This program and the accompanying materials are made available under the
 * terms of the Eclipse Public License v1.0 which accompanies this distribution,
 * and is available at http://www.eclipse.org/legal/epl-v10.html
 */
 module openflow-experimenter-match {
    namespace "urn:opendaylight:openflow:experimenter:match";
    prefix "expmatch";

    import yang-ext {prefix ext;}
    import ietf-yang-types {prefix yang;}
    import ietf-inet-types {prefix inet;}
    import openflow-types {prefix oft;}
    import openflow-augments {prefix aug;}
    import openflow-extensible-match {prefix oxm;}

    revision "2016-07-31" {
        description "#NOT_PUBLISHED# OpenFlow 1.3 - experimenter match model";
    }

    //ONF approved OpenFlow Match Extension (Extension - 109)
    identity tcp_flags {
        base oxm:match-field;
        description "TCP flags from the TCP header";
    }

    //ONF Approved OpenFlow Extensions

    //ONF approved OpenFlow Match Extension (Extension - 109)
    augment "/oxm:oxm-container/oxm:match-entry-value/aug:experimenter-id-case" {
        ext:augment-identifier "tcp-flags-match-entry";
        container tcp-flags {
            leaf flags {
                type uint16;
            }
            leaf mask {
                type binary;
            }
        }
    }
}
