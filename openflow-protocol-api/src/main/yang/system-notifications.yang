/*
 * Copyright (c) 2013 Pantheon Technologies s.r.o. and others. All rights reserved.
 *
 * This program and the accompanying materials are made available under the
 * terms of the Eclipse Public License v1.0 which accompanies this distribution,
 * and is available at http://www.eclipse.org/legal/epl-v10.html
 */

 module system-notifications {
    namespace "urn:opendaylight:openflow:system";
    prefix "ofs";

    revision "2013-09-27" {
        description "Model of system messages used in OpenFlow Protocol Library";
    }

    notification disconnect-event {
        description "Disconnect notification";
        leaf info {
            type string;
        }
    }

    notification switch-idle-event {
        description "Switch-idle notification";
        leaf info {
            type string;
        }
    }

}
